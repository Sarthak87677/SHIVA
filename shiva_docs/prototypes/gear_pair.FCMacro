# FreeCAD macro generated by SHIVA-1 (Macro > Macros... > Execute, or freecadcmd gear_pair.FCMacro)
import os
import FreeCAD as App
import Mesh
import Part

here = os.path.dirname(os.path.abspath(__file__)) if "__file__" in globals() else os.getcwd()
doc = App.newDocument("SHIVA_gear_pair")
mesh = Mesh.Mesh(os.path.join(here, "gear_pair.stl"))
shape = Part.Shape()
shape.makeShapeFromMesh(mesh.Topology, 0.05)
try:
    solid = Part.makeSolid(shape).removeSplitter()
except Exception:
    solid = shape
part = doc.addObject("Part::Feature", "gear_pair")
part.Shape = solid
sheet = doc.addObject("Spreadsheet::Sheet", "Parameters")
sheet.set("A1", "parameter"); sheet.set("B1", "value (SI)")
sheet.set('A2', 'module'); sheet.set('B2', '0.002')
sheet.set('A3', 'z1'); sheet.set('B3', '40.0')
sheet.set('A4', 'face_factor'); sheet.set('B4', '14.0')
sheet.set('A5', 'pressure_angle'); sheet.set('B5', '20.0')
sheet.set('A6', 'shift'); sheet.set('B6', '0.35000000000000003')
sheet.set("D1", "material"); sheet.set("E1", 'Alloy steel 4140 (Q&T)')
doc.recompute()
doc.saveAs(os.path.join(here, "gear_pair.FCStd"))
