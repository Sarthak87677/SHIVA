# FreeCAD macro generated by SHIVA-1 (Macro > Macros... > Execute, or freecadcmd propulsion_nozzle.FCMacro)
import os
import FreeCAD as App
import Mesh
import Part

here = os.path.dirname(os.path.abspath(__file__)) if "__file__" in globals() else os.getcwd()
doc = App.newDocument("SHIVA_propulsion_nozzle")
mesh = Mesh.Mesh(os.path.join(here, "propulsion_nozzle.stl"))
shape = Part.Shape()
shape.makeShapeFromMesh(mesh.Topology, 0.05)
try:
    solid = Part.makeSolid(shape).removeSplitter()
except Exception:
    solid = shape
part = doc.addObject("Part::Feature", "propulsion_nozzle")
part.Shape = solid
sheet = doc.addObject("Spreadsheet::Sheet", "Parameters")
sheet.set("A1", "parameter"); sheet.set("B1", "value (SI)")
sheet.set('A2', 'chamber_pressure'); sheet.set('B2', '15055757.739819478')
sheet.set('A3', 'expansion_ratio'); sheet.set('B3', '12.567301768733738')
sheet.set('A4', 'throat_radius'); sheet.set('B4', '0.0059')
sheet.set('A5', 'chamber_temperature'); sheet.set('B5', '2344.357942535357')
sheet.set('A6', 'molar_mass'); sheet.set('B6', '0.027887184959573465')
sheet.set('A7', 'half_angle'); sheet.set('B7', '15.0')
sheet.set('A8', 'wall_thickness'); sheet.set('B8', '0.0021')
sheet.set("D1", "material"); sheet.set("E1", 'Stainless steel 304')
doc.recompute()
doc.saveAs(os.path.join(here, "propulsion_nozzle.FCStd"))
