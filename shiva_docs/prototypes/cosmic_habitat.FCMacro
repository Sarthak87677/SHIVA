# FreeCAD macro generated by SHIVA-1 (Macro > Macros... > Execute, or freecadcmd cosmic_habitat.FCMacro)
import os
import FreeCAD as App
import Mesh
import Part

here = os.path.dirname(os.path.abspath(__file__)) if "__file__" in globals() else os.getcwd()
doc = App.newDocument("SHIVA_cosmic_habitat")
mesh = Mesh.Mesh(os.path.join(here, "cosmic_habitat.stl"))
shape = Part.Shape()
shape.makeShapeFromMesh(mesh.Topology, 0.05)
try:
    solid = Part.makeSolid(shape).removeSplitter()
except Exception:
    solid = shape
part = doc.addObject("Part::Feature", "cosmic_habitat")
part.Shape = solid
sheet = doc.addObject("Spreadsheet::Sheet", "Parameters")
sheet.set("A1", "parameter"); sheet.set("B1", "value (SI)")
sheet.set('A2', 'radius'); sheet.set('B2', '171')
sheet.set('A3', 'rpm'); sheet.set('B3', '2.18')
sheet.set('A4', 'thickness'); sheet.set('B4', '0.024')
sheet.set('A5', 'width'); sheet.set('B5', '190')
sheet.set('A6', 'pressure'); sheet.set('B6', '52562.11702168915')
sheet.set("D1", "material"); sheet.set("E1", 'CFRP unidirectional (fibre direction)')
doc.recompute()
doc.saveAs(os.path.join(here, "cosmic_habitat.FCStd"))
