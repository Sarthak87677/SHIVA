# FreeCAD macro generated by SHIVA-1 (Macro > Macros... > Execute, or freecadcmd drone_frame.FCMacro)
import os
import FreeCAD as App
import Mesh
import Part

here = os.path.dirname(os.path.abspath(__file__)) if "__file__" in globals() else os.getcwd()
doc = App.newDocument("SHIVA_drone_frame")
mesh = Mesh.Mesh(os.path.join(here, "drone_frame.stl"))
shape = Part.Shape()
shape.makeShapeFromMesh(mesh.Topology, 0.05)
try:
    solid = Part.makeSolid(shape).removeSplitter()
except Exception:
    solid = shape
part = doc.addObject("Part::Feature", "drone_frame")
part.Shape = solid
sheet = doc.addObject("Spreadsheet::Sheet", "Parameters")
sheet.set("A1", "parameter"); sheet.set("B1", "value (SI)")
sheet.set('A2', 'arm_length'); sheet.set('B2', '0.31')
sheet.set('A3', 'arm_od'); sheet.set('B3', '0.028')
sheet.set('A4', 'wall_ratio'); sheet.set('B4', '0.05357142857142857')
sheet.set('A5', 'prop_diameter'); sheet.set('B5', '0.381')
sheet.set('A6', 'n_arms'); sheet.set('B6', '3.0')
sheet.set('A7', 'battery_wh'); sheet.set('B7', '325.6')
sheet.set("D1", "material"); sheet.set("E1", 'Aluminium 6061-T6')
doc.recompute()
doc.saveAs(os.path.join(here, "drone_frame.FCStd"))
