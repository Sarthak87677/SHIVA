# FreeCAD macro generated by SHIVA-1 (Macro > Macros... > Execute, or freecadcmd pump_impeller.FCMacro)
import os
import FreeCAD as App
import Mesh
import Part

here = os.path.dirname(os.path.abspath(__file__)) if "__file__" in globals() else os.getcwd()
doc = App.newDocument("SHIVA_pump_impeller")
mesh = Mesh.Mesh(os.path.join(here, "pump_impeller.stl"))
shape = Part.Shape()
shape.makeShapeFromMesh(mesh.Topology, 0.05)
try:
    solid = Part.makeSolid(shape).removeSplitter()
except Exception:
    solid = shape
part = doc.addObject("Part::Feature", "pump_impeller")
part.Shape = solid
sheet = doc.addObject("Spreadsheet::Sheet", "Parameters")
sheet.set("A1", "parameter"); sheet.set("B1", "value (SI)")
sheet.set('A2', 'r1'); sheet.set('B2', '0.0341')
sheet.set('A3', 'r2'); sheet.set('B3', '0.1357')
sheet.set('A4', 'b2'); sheet.set('B4', '0.0064')
sheet.set('A5', 'beta1'); sheet.set('B5', '32.5')
sheet.set('A6', 'beta2'); sheet.set('B6', '21.5')
sheet.set('A7', 'blades'); sheet.set('B7', '7.0')
sheet.set('A8', 'rpm'); sheet.set('B8', '1645.4463959506852')
sheet.set("D1", "material"); sheet.set("E1", 'Aluminium 6061-T6')
doc.recompute()
doc.saveAs(os.path.join(here, "pump_impeller.FCStd"))
