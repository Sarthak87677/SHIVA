# FreeCAD macro generated by SHIVA-1 (Macro > Macros... > Execute, or freecadcmd structure_truss.FCMacro)
import os
import FreeCAD as App
import Mesh
import Part

here = os.path.dirname(os.path.abspath(__file__)) if "__file__" in globals() else os.getcwd()
doc = App.newDocument("SHIVA_structure_truss")
mesh = Mesh.Mesh(os.path.join(here, "structure_truss.stl"))
shape = Part.Shape()
shape.makeShapeFromMesh(mesh.Topology, 0.05)
try:
    solid = Part.makeSolid(shape).removeSplitter()
except Exception:
    solid = shape
part = doc.addObject("Part::Feature", "structure_truss")
part.Shape = solid
sheet = doc.addObject("Spreadsheet::Sheet", "Parameters")
sheet.set("A1", "parameter"); sheet.set("B1", "value (SI)")
sheet.set('A2', 'h0'); sheet.set('B2', '0.985')
sheet.set('A3', 'h1'); sheet.set('B3', '0.755')
sheet.set('A4', 'h2'); sheet.set('B4', '0.4')
sheet.set('A5', 'area_top'); sheet.set('B5', '0.00015393804002589986')
sheet.set('A6', 'area_bottom'); sheet.set('B6', '0.00041547562843725016')
sheet.set('A7', 'area_web'); sheet.set('B7', '0.00020106192982974677')
sheet.set("D1", "material"); sheet.set("E1", 'CFRP quasi-isotropic laminate')
doc.recompute()
doc.saveAs(os.path.join(here, "structure_truss.FCStd"))
