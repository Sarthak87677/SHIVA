# FreeCAD macro generated by SHIVA-1 (Macro > Macros... > Execute, or freecadcmd cosmic_lightsail.FCMacro)
import os
import FreeCAD as App
import Mesh
import Part

here = os.path.dirname(os.path.abspath(__file__)) if "__file__" in globals() else os.getcwd()
doc = App.newDocument("SHIVA_cosmic_lightsail")
mesh = Mesh.Mesh(os.path.join(here, "cosmic_lightsail.stl"))
shape = Part.Shape()
shape.makeShapeFromMesh(mesh.Topology, 0.05)
try:
    solid = Part.makeSolid(shape).removeSplitter()
except Exception:
    solid = shape
part = doc.addObject("Part::Feature", "cosmic_lightsail")
part.Shape = solid
sheet = doc.addObject("Spreadsheet::Sheet", "Parameters")
sheet.set("A1", "parameter"); sheet.set("B1", "value (SI)")
sheet.set('A2', 'film_thickness'); sheet.set('B2', '9.000000000000001e-07')
sheet.set('A3', 'side_length'); sheet.set('B3', '443.4317103671343')
sheet.set('A4', 'reflectivity'); sheet.set('B4', '0.91')
sheet.set('A5', 'boom_linear_density'); sheet.set('B5', '0.060286495278378635')
sheet.set('A6', 'distance_au'); sheet.set('B6', '0.4438089534922589')
sheet.set("D1", "material"); sheet.set("E1", 'Polyimide film (Kapton HN)')
doc.recompute()
doc.saveAs(os.path.join(here, "cosmic_lightsail.FCStd"))
