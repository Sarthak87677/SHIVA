# FreeCAD macro generated by SHIVA-1 (Macro > Macros... > Execute, or freecadcmd energy_flywheel.FCMacro)
import os
import FreeCAD as App
import Mesh
import Part

here = os.path.dirname(os.path.abspath(__file__)) if "__file__" in globals() else os.getcwd()
doc = App.newDocument("SHIVA_energy_flywheel")
mesh = Mesh.Mesh(os.path.join(here, "energy_flywheel.stl"))
shape = Part.Shape()
shape.makeShapeFromMesh(mesh.Topology, 0.05)
try:
    solid = Part.makeSolid(shape).removeSplitter()
except Exception:
    solid = shape
part = doc.addObject("Part::Feature", "energy_flywheel")
part.Shape = solid
sheet = doc.addObject("Spreadsheet::Sheet", "Parameters")
sheet.set("A1", "parameter"); sheet.set("B1", "value (SI)")
sheet.set('A2', 'outer_radius'); sheet.set('B2', '0.641')
sheet.set('A3', 'inner_ratio'); sheet.set('B3', '0.1308297860989842')
sheet.set('A4', 'thickness'); sheet.set('B4', '0.4')
sheet.set('A5', 'rpm'); sheet.set('B5', '4800')
sheet.set('A6', 'housing_pressure_ratio'); sheet.set('B6', '9.999999999999997e-06')
sheet.set("D1", "material"); sheet.set("E1", 'Aluminium 7075-T6')
doc.recompute()
doc.saveAs(os.path.join(here, "energy_flywheel.FCStd"))
